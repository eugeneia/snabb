module vita-gentest {
  namespace vita:gentest;
  prefix gentest;

  import vita-esp-gateway { prefix vita; }

  container private-interface4 {
    uses vita:interface; uses vita:interface4;
  }
  choice router {
    list public-interface4 {
      key ip4; unique queue;
      uses vita:interface; uses vita:interface4;
      leaf queue { type vita:queue; default 1; }
    }
    list public-interface6 {
      key ip6; unique queue;
      uses vita:interface; uses vita:interface6;
      leaf queue { type vita:queue; default 1; }
    }
  }

  leaf negotiation-ttl { type vita:time-to-live; }
  leaf sa-ttl { type vita:time-to-live; }

  leaf route-prefix { type string; }
  leaf nroutes { type uint32 { range "1..max"; } }
  leaf packet-size { type string; }
}
